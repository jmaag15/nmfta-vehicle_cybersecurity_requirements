[DOCUMENT]
TITLE: Cloud and Backend Security Requirements

[GRAMMAR]
IMPORT_FROM_FILE: @vcr_grammar

[REQUIREMENT]
UID: CLOUD-AA-010
STATEMENT: >>>
This Cloud or Back-end component must satisfy requirement AA-010
<<<
RELATIONS:
- TYPE: Parent
  VALUE: AA-010
  ROLE: Refines

[REQUIREMENT]
UID: CLOUD-AC-010
STATEMENT: >>>
This Cloud or Back-end component must satisfy requirement AC-010
<<<
RELATIONS:
- TYPE: Parent
  VALUE: AC-010
  ROLE: Refines

[REQUIREMENT]
UID: CLOUD-AC-030
STATEMENT: >>>
This Cloud or Back-end component must satisfy requirement AC-030
<<<
RELATIONS:
- TYPE: Parent
  VALUE: AC-030
  ROLE: Refines

[REQUIREMENT]
UID: CLOUD-AC-040
STATEMENT: >>>
This Cloud or Back-end component must satisfy requirement AC-040
<<<
RELATIONS:
- TYPE: Parent
  VALUE: AC-040
  ROLE: Refines

[REQUIREMENT]
UID: CLOUD-AC-041
STATEMENT: >>>
This Cloud or Back-end component must satisfy requirement AC-041
<<<
RELATIONS:
- TYPE: Parent
  VALUE: AC-041
  ROLE: Refines

[REQUIREMENT]
UID: CLOUD-AC-050
STATEMENT: >>>
This Cloud or Back-end component must satisfy requirement AC-050
<<<
RELATIONS:
- TYPE: Parent
  VALUE: AC-050
  ROLE: Refines

[REQUIREMENT]
UID: CLOUD-AC-070
STATEMENT: >>>
This Cloud or Back-end component must satisfy requirement AC-070
<<<
RELATIONS:
- TYPE: Parent
  VALUE: AC-070
  ROLE: Refines

[REQUIREMENT]
UID: CLOUD-CM-020
STATEMENT: >>>
This Cloud or Back-end component must satisfy requirement CM-020
<<<
RELATIONS:
- TYPE: Parent
  VALUE: CM-020
  ROLE: Refines

[REQUIREMENT]
UID: CLOUD-CM-030
STATEMENT: >>>
This Cloud or Back-end component must satisfy requirement CM-030
<<<
RELATIONS:
- TYPE: Parent
  VALUE: CM-030
  ROLE: Refines

[REQUIREMENT]
UID: CLOUD-CM-040
STATEMENT: >>>
This Cloud or Back-end component must satisfy requirement CM-040
<<<
RELATIONS:
- TYPE: Parent
  VALUE: CM-040
  ROLE: Refines

[REQUIREMENT]
UID: CLOUD-IA-010
STATEMENT: >>>
This Cloud or Back-end component must satisfy requirement IA-010
<<<
RELATIONS:
- TYPE: Parent
  VALUE: IA-010
  ROLE: Refines

[REQUIREMENT]
UID: CLOUD-IA-030
STATEMENT: >>>
This Cloud or Back-end component must satisfy requirement IA-030
<<<
RELATIONS:
- TYPE: Parent
  VALUE: IA-030
  ROLE: Refines

[REQUIREMENT]
UID: CLOUD-IR-010
STATEMENT: >>>
This Cloud or Back-end component must satisfy requirement IR-010
<<<
RELATIONS:
- TYPE: Parent
  VALUE: IR-010
  ROLE: Refines

[REQUIREMENT]
UID: CLOUD-M-010
STATEMENT: >>>
This Cloud or Back-end component must satisfy requirement M-010
<<<
RELATIONS:
- TYPE: Parent
  VALUE: M-010
  ROLE: Refines

[REQUIREMENT]
UID: CLOUD-M-020
STATEMENT: >>>
This Cloud or Back-end component must satisfy requirement M-020
<<<
RELATIONS:
- TYPE: Parent
  VALUE: M-020
  ROLE: Refines

[REQUIREMENT]
UID: CLOUD-M-030
STATEMENT: >>>
This Cloud or Back-end component must satisfy requirement M-030
<<<
RELATIONS:
- TYPE: Parent
  VALUE: M-030
  ROLE: Refines

[REQUIREMENT]
UID: CLOUD-M-031
STATEMENT: >>>
This Cloud or Back-end component must satisfy requirement M-031
<<<
RELATIONS:
- TYPE: Parent
  VALUE: M-031
  ROLE: Refines

[REQUIREMENT]
UID: CLOUD-M-032
STATEMENT: >>>
This Cloud or Back-end component must satisfy requirement M-032
<<<
RELATIONS:
- TYPE: Parent
  VALUE: M-032
  ROLE: Refines

[REQUIREMENT]
UID: CLOUD-P-010
STATEMENT: >>>
This Cloud or Back-end component must satisfy requirement P-010
<<<
RELATIONS:
- TYPE: Parent
  VALUE: P-010
  ROLE: Refines

[REQUIREMENT]
UID: CLOUD-P-020
STATEMENT: >>>
This Cloud or Back-end component must satisfy requirement P-020
<<<
RELATIONS:
- TYPE: Parent
  VALUE: P-020
  ROLE: Refines

[REQUIREMENT]
UID: CLOUD-P-030
STATEMENT: >>>
This Cloud or Back-end component must satisfy requirement P-030
<<<
RELATIONS:
- TYPE: Parent
  VALUE: P-030
  ROLE: Refines

[REQUIREMENT]
UID: CLOUD-PS-010
STATEMENT: >>>
This Cloud or Back-end component must satisfy requirement PS-010
<<<
RELATIONS:
- TYPE: Parent
  VALUE: PS-010
  ROLE: Refines

[REQUIREMENT]
UID: CLOUD-RA-010
STATEMENT: >>>
This Cloud or Back-end component must satisfy requirement RA-010
<<<
RELATIONS:
- TYPE: Parent
  VALUE: RA-010
  ROLE: Refines

[REQUIREMENT]
UID: CLOUD-RA-020
STATEMENT: >>>
This Cloud or Back-end component must satisfy requirement RA-020
<<<
RELATIONS:
- TYPE: Parent
  VALUE: RA-020
  ROLE: Refines

[REQUIREMENT]
UID: CLOUD-SAA-010
STATEMENT: >>>
This Cloud or Back-end component must satisfy requirement SAA-010
<<<
RELATIONS:
- TYPE: Parent
  VALUE: SAA-010
  ROLE: Refines

[REQUIREMENT]
UID: CLOUD-SAA-020
STATEMENT: >>>
This Cloud or Back-end component must satisfy requirement SAA-020
<<<
RELATIONS:
- TYPE: Parent
  VALUE: SAA-020
  ROLE: Refines

[REQUIREMENT]
UID: CLOUD-SAA-030
STATEMENT: >>>
This Cloud or Back-end component must satisfy requirement SAA-030
<<<
RELATIONS:
- TYPE: Parent
  VALUE: SAA-030
  ROLE: Refines

[REQUIREMENT]
UID: CLOUD-SAA-040
STATEMENT: >>>
This Cloud or Back-end component must satisfy requirement SAA-040
<<<
RELATIONS:
- TYPE: Parent
  VALUE: SAA-040
  ROLE: Refines

[REQUIREMENT]
UID: CLOUD-SAA-050
STATEMENT: >>>
This Cloud or Back-end component must satisfy requirement SAA-050
<<<
RELATIONS:
- TYPE: Parent
  VALUE: SAA-050
  ROLE: Refines

[REQUIREMENT]
UID: CLOUD-SCP-010
STATEMENT: >>>
This Cloud or Back-end component must satisfy requirement SCP-010
<<<
RELATIONS:
- TYPE: Parent
  VALUE: SCP-010
  ROLE: Refines

[REQUIREMENT]
UID: CLOUD-SCP-011
STATEMENT: >>>
This Cloud or Back-end component must satisfy requirement SCP-011
<<<
RELATIONS:
- TYPE: Parent
  VALUE: SCP-011
  ROLE: Refines

[REQUIREMENT]
UID: CLOUD-SCP-020
STATEMENT: >>>
This Cloud or Back-end component must satisfy requirement SCP-020
<<<
RELATIONS:
- TYPE: Parent
  VALUE: SCP-020
  ROLE: Refines

[REQUIREMENT]
UID: CLOUD-SCP-030
STATEMENT: >>>
This Cloud or Back-end component must satisfy requirement SCP-030
<<<
RELATIONS:
- TYPE: Parent
  VALUE: SCP-030
  ROLE: Refines

[REQUIREMENT]
UID: CLOUD-SCP-040
STATEMENT: >>>
This Cloud or Back-end component must satisfy requirement SCP-040
<<<
RELATIONS:
- TYPE: Parent
  VALUE: SCP-040
  ROLE: Refines

[REQUIREMENT]
UID: CLOUD-SCP-050
STATEMENT: >>>
This Cloud or Back-end component must satisfy requirement SCP-050
<<<
RELATIONS:
- TYPE: Parent
  VALUE: SCP-050
  ROLE: Refines

[REQUIREMENT]
UID: CLOUD-SCP-090
STATEMENT: >>>
This Cloud or Back-end component must satisfy requirement SCP-090
<<<
RELATIONS:
- TYPE: Parent
  VALUE: SCP-090
  ROLE: Refines

[REQUIREMENT]
UID: CLOUD-SCP-091
STATEMENT: >>>
This Cloud or Back-end component must satisfy requirement SCP-091
<<<
RELATIONS:
- TYPE: Parent
  VALUE: SCP-091
  ROLE: Refines

[REQUIREMENT]
UID: CLOUD-SCP-092
STATEMENT: >>>
This Cloud or Back-end component must satisfy requirement SCP-092
<<<
RELATIONS:
- TYPE: Parent
  VALUE: SCP-092
  ROLE: Refines

[REQUIREMENT]
UID: CLOUD-SCP-110
STATEMENT: >>>
This Cloud or Back-end component must satisfy requirement SCP-110
<<<
RELATIONS:
- TYPE: Parent
  VALUE: SCP-110
  ROLE: Refines

[REQUIREMENT]
UID: CLOUD-SCP-120
STATEMENT: >>>
This Cloud or Back-end component must satisfy requirement SCP-120
<<<
RELATIONS:
- TYPE: Parent
  VALUE: SCP-120
  ROLE: Refines

[REQUIREMENT]
UID: CLOUD-SCP-130
STATEMENT: >>>
This Cloud or Back-end component must satisfy requirement SCP-130
<<<
RELATIONS:
- TYPE: Parent
  VALUE: SCP-130
  ROLE: Refines

[REQUIREMENT]
UID: CLOUD-SII-010
STATEMENT: >>>
This Cloud or Back-end component must satisfy requirement SII-010
<<<
RELATIONS:
- TYPE: Parent
  VALUE: SII-010
  ROLE: Refines

[REQUIREMENT]
UID: CLOUD-SII-011
STATEMENT: >>>
This Cloud or Back-end component must satisfy requirement SII-011
<<<
RELATIONS:
- TYPE: Parent
  VALUE: SII-011
  ROLE: Refines

[REQUIREMENT]
UID: CLOUD-SII-020
STATEMENT: >>>
This Cloud or Back-end component must satisfy requirement SII-020
<<<
RELATIONS:
- TYPE: Parent
  VALUE: SII-020
  ROLE: Refines

[REQUIREMENT]
UID: CLOUD-SII-021
STATEMENT: >>>
This Cloud or Back-end component must satisfy requirement SII-021
<<<
RELATIONS:
- TYPE: Parent
  VALUE: SII-021
  ROLE: Refines

[REQUIREMENT]
UID: CLOUD-SII-070
STATEMENT: >>>
This Cloud or Back-end component must satisfy requirement SII-070
<<<
RELATIONS:
- TYPE: Parent
  VALUE: SII-070
  ROLE: Refines

[REQUIREMENT]
UID: CLOUD-SII-071
STATEMENT: >>>
This Cloud or Back-end component must satisfy requirement SII-071
<<<
RELATIONS:
- TYPE: Parent
  VALUE: SII-071
  ROLE: Refines

[REQUIREMENT]
UID: CLOUD-SII-080
STATEMENT: >>>
This Cloud or Back-end component must satisfy requirement SII-080
<<<
RELATIONS:
- TYPE: Parent
  VALUE: SII-080
  ROLE: Refines

[REQUIREMENT]
UID: CLOUD-SII-081
STATEMENT: >>>
This Cloud or Back-end component must satisfy requirement SII-081
<<<
RELATIONS:
- TYPE: Parent
  VALUE: SII-081
  ROLE: Refines

[REQUIREMENT]
UID: CLOUD-SII-090
STATEMENT: >>>
This Cloud or Back-end component must satisfy requirement SII-090
<<<
RELATIONS:
- TYPE: Parent
  VALUE: SII-090
  ROLE: Refines

[REQUIREMENT]
UID: CLOUD-SII-100
STATEMENT: >>>
This Cloud or Back-end component must satisfy requirement SII-100
<<<
RELATIONS:
- TYPE: Parent
  VALUE: SII-100
  ROLE: Refines

[REQUIREMENT]
UID: CLOUD-SII-110
STATEMENT: >>>
This Cloud or Back-end component must satisfy requirement SII-110
<<<
RELATIONS:
- TYPE: Parent
  VALUE: SII-110
  ROLE: Refines

[REQUIREMENT]
UID: CLOUD-SII-120
STATEMENT: >>>
This Cloud or Back-end component must satisfy requirement SII-120
<<<
RELATIONS:
- TYPE: Parent
  VALUE: SII-120
  ROLE: Refines

[REQUIREMENT]
UID: CLOUD-SII-130
STATEMENT: >>>
This Cloud or Back-end component must satisfy requirement SII-130
<<<
RELATIONS:
- TYPE: Parent
  VALUE: SII-130
  ROLE: Refines

[REQUIREMENT]
UID: CLOUD-SII-140
STATEMENT: >>>
This Cloud or Back-end component must satisfy requirement SII-140
<<<
RELATIONS:
- TYPE: Parent
  VALUE: SII-140
  ROLE: Refines

[REQUIREMENT]
UID: CLOUD-SII-150
STATEMENT: >>>
This Cloud or Back-end component must satisfy requirement SII-150
<<<
RELATIONS:
- TYPE: Parent
  VALUE: SII-150
  ROLE: Refines

[REQUIREMENT]
UID: CLOUD-SII-170
STATEMENT: >>>
This Cloud or Back-end component must satisfy requirement SII-170
<<<
RELATIONS:
- TYPE: Parent
  VALUE: SII-170
  ROLE: Refines

[REQUIREMENT]
UID: CLOUD-SII-171
STATEMENT: >>>
This Cloud or Back-end component must satisfy requirement SII-171
<<<
RELATIONS:
- TYPE: Parent
  VALUE: SII-171
  ROLE: Refines

[REQUIREMENT]
UID: CLOUD-SII-180
STATEMENT: >>>
This Cloud or Back-end component must satisfy requirement SII-180
<<<
RELATIONS:
- TYPE: Parent
  VALUE: SII-180
  ROLE: Refines

[REQUIREMENT]
UID: CLOUD-SII-200
STATEMENT: >>>
This Cloud or Back-end component must satisfy requirement SII-200
<<<
RELATIONS:
- TYPE: Parent
  VALUE: SII-200
  ROLE: Refines
