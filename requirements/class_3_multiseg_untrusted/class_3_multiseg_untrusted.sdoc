[DOCUMENT]
TITLE: Class 3 Multi Segment with Untrusted Wired Connection Security Requirements

[GRAMMAR]
IMPORT_FROM_FILE: @vcr_grammar

[TEXT]
STATEMENT: >>>
This document specifies cybersecurity requirements for Class 3 vehicle components: **Multi Segment with Untrusted Wired Connection**.

Class 3 devices are truck modules that are not intended to be Vehicle Gateways but nonetheless are connected to two or more vehicle network segments where one or more of those segments are untrusted (e.g. diagnostic ports, trailer bridges, or networks exposed to external physical connections).

Examples include:
- Tractor/Trailer Bridge #1 / #2 (J1939 SA 32, 138, 39)
- Powertrain Control Module (CPC) (J1939 SA 90)
- Engine #1 (MCM / EMS / ECM) (J1939 SA 00, 01)
- Transmission #1 (TCM) (J1939 SA 03)
- Cab Controller Primary / Secondary (SAM CAB) (J1939 SA 49, 50)
- Instrument Cluster #1 (Gauges) (J1939 SA 23)
- On Board Diagnostic Unit (J1939 SA 250)
- ADAS Adaptive Cruise Control / Lane Keep (Bendix Fusion) (J1939 SA 42, 232, 19)
<<<

[[SECTION]]
TITLE: Baseline Security Requirements Applicability

[REQUIREMENT]
UID: C3-AA-010
STATUS: Draft
TAGS: NEEDS_WORKING_GROUP_REVIEW
STATEMENT: >>>
Class 3 devices SHALL satisfy baseline requirement AA-010.
<<<
RELATIONS:
- TYPE: Parent
  VALUE: AA-010
  ROLE: Refines

[REQUIREMENT]
UID: C3-AC-010
STATUS: Draft
TAGS: NEEDS_WORKING_GROUP_REVIEW
STATEMENT: >>>
Class 3 devices SHALL satisfy baseline requirement AC-010.
<<<
RELATIONS:
- TYPE: Parent
  VALUE: AC-010
  ROLE: Refines

[REQUIREMENT]
UID: C3-AC-020
STATUS: Draft
TAGS: NEEDS_WORKING_GROUP_REVIEW
STATEMENT: >>>
Class 3 devices SHALL satisfy baseline requirement AC-020.
<<<
RELATIONS:
- TYPE: Parent
  VALUE: AC-020
  ROLE: Refines

[REQUIREMENT]
UID: C3-AC-030
STATUS: Draft
TAGS: NEEDS_WORKING_GROUP_REVIEW
STATEMENT: >>>
Class 3 devices SHALL satisfy baseline requirement AC-030.
<<<
RELATIONS:
- TYPE: Parent
  VALUE: AC-030
  ROLE: Refines

[REQUIREMENT]
UID: C3-AC-040
STATUS: Draft
TAGS: NEEDS_WORKING_GROUP_REVIEW
STATEMENT: >>>
Class 3 devices SHALL satisfy baseline requirement AC-040.
<<<
RELATIONS:
- TYPE: Parent
  VALUE: AC-040
  ROLE: Refines

[REQUIREMENT]
UID: C3-AC-041
STATUS: Draft
TAGS: NEEDS_WORKING_GROUP_REVIEW
STATEMENT: >>>
Class 3 devices SHALL satisfy baseline requirement AC-041.
<<<
RELATIONS:
- TYPE: Parent
  VALUE: AC-041
  ROLE: Refines

[REQUIREMENT]
UID: C3-AC-050
STATUS: Draft
TAGS: NEEDS_WORKING_GROUP_REVIEW
STATEMENT: >>>
Class 3 devices SHALL satisfy baseline requirement AC-050.
<<<
RELATIONS:
- TYPE: Parent
  VALUE: AC-050
  ROLE: Refines

[REQUIREMENT]
UID: C3-AC-070
STATUS: Draft
TAGS: NEEDS_WORKING_GROUP_REVIEW
STATEMENT: >>>
Class 3 devices SHALL satisfy baseline requirement AC-070.
<<<
RELATIONS:
- TYPE: Parent
  VALUE: AC-070
  ROLE: Refines

[REQUIREMENT]
UID: C3-AC-080
STATUS: Draft
TAGS: NEEDS_WORKING_GROUP_REVIEW
STATEMENT: >>>
Class 3 devices SHALL satisfy baseline requirement AC-080.
<<<
RELATIONS:
- TYPE: Parent
  VALUE: AC-080
  ROLE: Refines

[REQUIREMENT]
UID: C3-CM-010
STATUS: Draft
TAGS: NEEDS_WORKING_GROUP_REVIEW
STATEMENT: >>>
Class 3 devices SHALL satisfy baseline requirement CM-010.
<<<
RELATIONS:
- TYPE: Parent
  VALUE: CM-010
  ROLE: Refines

[REQUIREMENT]
UID: C3-CM-020
STATUS: Draft
TAGS: NEEDS_WORKING_GROUP_REVIEW
STATEMENT: >>>
Class 3 devices SHALL satisfy baseline requirement CM-020.
<<<
RELATIONS:
- TYPE: Parent
  VALUE: CM-020
  ROLE: Refines

[REQUIREMENT]
UID: C3-CM-030
STATUS: Draft
TAGS: NEEDS_WORKING_GROUP_REVIEW
STATEMENT: >>>
Class 3 devices SHALL satisfy baseline requirement CM-030.
<<<
RELATIONS:
- TYPE: Parent
  VALUE: CM-030
  ROLE: Refines

[REQUIREMENT]
UID: C3-CM-040
STATUS: Draft
TAGS: NEEDS_WORKING_GROUP_REVIEW
STATEMENT: >>>
Class 3 devices SHALL satisfy baseline requirement CM-040.
<<<
RELATIONS:
- TYPE: Parent
  VALUE: CM-040
  ROLE: Refines

[REQUIREMENT]
UID: C3-IA-010
STATUS: Draft
TAGS: NEEDS_WORKING_GROUP_REVIEW
STATEMENT: >>>
Class 3 devices SHALL satisfy baseline requirement IA-010.
<<<
RELATIONS:
- TYPE: Parent
  VALUE: IA-010
  ROLE: Refines

[REQUIREMENT]
UID: C3-IA-020
STATUS: Draft
TAGS: NEEDS_WORKING_GROUP_REVIEW
STATEMENT: >>>
Class 3 devices SHALL satisfy baseline requirement IA-020.
<<<
RELATIONS:
- TYPE: Parent
  VALUE: IA-020
  ROLE: Refines

[REQUIREMENT]
UID: C3-IA-030
STATUS: Draft
TAGS: NEEDS_WORKING_GROUP_REVIEW
STATEMENT: >>>
Class 3 devices SHALL satisfy baseline requirement IA-030.
<<<
RELATIONS:
- TYPE: Parent
  VALUE: IA-030
  ROLE: Refines

[REQUIREMENT]
UID: C3-IR-010
STATUS: Draft
TAGS: NEEDS_WORKING_GROUP_REVIEW
STATEMENT: >>>
Class 3 devices SHALL satisfy baseline requirement IR-010.
<<<
RELATIONS:
- TYPE: Parent
  VALUE: IR-010
  ROLE: Refines

[REQUIREMENT]
UID: C3-M-010
STATUS: Draft
TAGS: NEEDS_WORKING_GROUP_REVIEW
STATEMENT: >>>
Class 3 devices SHALL satisfy baseline requirement M-010.
<<<
RELATIONS:
- TYPE: Parent
  VALUE: M-010
  ROLE: Refines

[REQUIREMENT]
UID: C3-M-020
STATUS: Draft
TAGS: NEEDS_WORKING_GROUP_REVIEW
STATEMENT: >>>
Class 3 devices SHALL satisfy baseline requirement M-020.
<<<
RELATIONS:
- TYPE: Parent
  VALUE: M-020
  ROLE: Refines

[REQUIREMENT]
UID: C3-M-030
STATUS: Draft
TAGS: NEEDS_WORKING_GROUP_REVIEW
STATEMENT: >>>
Class 3 devices SHALL satisfy baseline requirement M-030.
<<<
RELATIONS:
- TYPE: Parent
  VALUE: M-030
  ROLE: Refines

[REQUIREMENT]
UID: C3-M-031
STATUS: Draft
TAGS: NEEDS_WORKING_GROUP_REVIEW
STATEMENT: >>>
Class 3 devices SHALL satisfy baseline requirement M-031.
<<<
RELATIONS:
- TYPE: Parent
  VALUE: M-031
  ROLE: Refines

[REQUIREMENT]
UID: C3-M-032
STATUS: Draft
TAGS: NEEDS_WORKING_GROUP_REVIEW
STATEMENT: >>>
Class 3 devices SHALL satisfy baseline requirement M-032.
<<<
RELATIONS:
- TYPE: Parent
  VALUE: M-032
  ROLE: Refines

[REQUIREMENT]
UID: C3-M-040
STATUS: Draft
TAGS: NEEDS_WORKING_GROUP_REVIEW
STATEMENT: >>>
Class 3 devices SHALL satisfy baseline requirement M-040.
<<<
RELATIONS:
- TYPE: Parent
  VALUE: M-040
  ROLE: Refines

[REQUIREMENT]
UID: C3-P-010
STATUS: Draft
TAGS: NEEDS_WORKING_GROUP_REVIEW
STATEMENT: >>>
Class 3 devices SHALL satisfy baseline requirement P-010.
<<<
RELATIONS:
- TYPE: Parent
  VALUE: P-010
  ROLE: Refines

[REQUIREMENT]
UID: C3-P-020
STATUS: Draft
TAGS: NEEDS_WORKING_GROUP_REVIEW
STATEMENT: >>>
Class 3 devices SHALL satisfy baseline requirement P-020.
<<<
RELATIONS:
- TYPE: Parent
  VALUE: P-020
  ROLE: Refines

[REQUIREMENT]
UID: C3-PS-010
STATUS: Draft
TAGS: NEEDS_WORKING_GROUP_REVIEW
STATEMENT: >>>
Class 3 devices SHALL satisfy baseline requirement PS-010.
<<<
RELATIONS:
- TYPE: Parent
  VALUE: PS-010
  ROLE: Refines

[REQUIREMENT]
UID: C3-RA-010
STATUS: Draft
TAGS: NEEDS_WORKING_GROUP_REVIEW
STATEMENT: >>>
Class 3 devices SHALL satisfy baseline requirement RA-010.
<<<
RELATIONS:
- TYPE: Parent
  VALUE: RA-010
  ROLE: Refines

[REQUIREMENT]
UID: C3-RA-020
STATUS: Draft
TAGS: NEEDS_WORKING_GROUP_REVIEW
STATEMENT: >>>
Class 3 devices SHALL satisfy baseline requirement RA-020.
<<<
RELATIONS:
- TYPE: Parent
  VALUE: RA-020
  ROLE: Refines

[REQUIREMENT]
UID: C3-SAA-010
STATUS: Draft
TAGS: NEEDS_WORKING_GROUP_REVIEW
STATEMENT: >>>
Class 3 devices SHALL satisfy baseline requirement SAA-010.
<<<
RELATIONS:
- TYPE: Parent
  VALUE: SAA-010
  ROLE: Refines

[REQUIREMENT]
UID: C3-SAA-020
STATUS: Draft
TAGS: NEEDS_WORKING_GROUP_REVIEW
STATEMENT: >>>
Class 3 devices SHALL satisfy baseline requirement SAA-020.
<<<
RELATIONS:
- TYPE: Parent
  VALUE: SAA-020
  ROLE: Refines

[REQUIREMENT]
UID: C3-SAA-030
STATUS: Draft
TAGS: NEEDS_WORKING_GROUP_REVIEW
STATEMENT: >>>
Class 3 devices SHALL satisfy baseline requirement SAA-030.
<<<
RELATIONS:
- TYPE: Parent
  VALUE: SAA-030
  ROLE: Refines

[REQUIREMENT]
UID: C3-SAA-040
STATUS: Draft
TAGS: NEEDS_WORKING_GROUP_REVIEW
STATEMENT: >>>
Class 3 devices SHALL satisfy baseline requirement SAA-040.
<<<
RELATIONS:
- TYPE: Parent
  VALUE: SAA-040
  ROLE: Refines

[REQUIREMENT]
UID: C3-SAA-050
STATUS: Draft
TAGS: NEEDS_WORKING_GROUP_REVIEW
STATEMENT: >>>
Class 3 devices SHALL satisfy baseline requirement SAA-050.
<<<
RELATIONS:
- TYPE: Parent
  VALUE: SAA-050
  ROLE: Refines

[REQUIREMENT]
UID: C3-SCP-010
STATUS: Draft
TAGS: NEEDS_WORKING_GROUP_REVIEW
STATEMENT: >>>
Class 3 devices SHALL satisfy baseline requirement SCP-010.
<<<
RELATIONS:
- TYPE: Parent
  VALUE: SCP-010
  ROLE: Refines

[REQUIREMENT]
UID: C3-SCP-011
STATUS: Draft
TAGS: NEEDS_WORKING_GROUP_REVIEW
STATEMENT: >>>
Class 3 devices SHALL satisfy baseline requirement SCP-011.
<<<
RELATIONS:
- TYPE: Parent
  VALUE: SCP-011
  ROLE: Refines

[REQUIREMENT]
UID: C3-SCP-020
STATUS: Draft
TAGS: NEEDS_WORKING_GROUP_REVIEW
STATEMENT: >>>
Class 3 devices SHALL satisfy baseline requirement SCP-020.
<<<
RELATIONS:
- TYPE: Parent
  VALUE: SCP-020
  ROLE: Refines

[REQUIREMENT]
UID: C3-SCP-030
STATUS: Draft
TAGS: NEEDS_WORKING_GROUP_REVIEW
STATEMENT: >>>
Class 3 devices SHALL satisfy baseline requirement SCP-030.
<<<
RELATIONS:
- TYPE: Parent
  VALUE: SCP-030
  ROLE: Refines

[REQUIREMENT]
UID: C3-SCP-040
STATUS: Draft
TAGS: NEEDS_WORKING_GROUP_REVIEW
STATEMENT: >>>
Class 3 devices SHALL satisfy baseline requirement SCP-040.
<<<
RELATIONS:
- TYPE: Parent
  VALUE: SCP-040
  ROLE: Refines

[REQUIREMENT]
UID: C3-SCP-060
STATUS: Draft
TAGS: NEEDS_WORKING_GROUP_REVIEW
STATEMENT: >>>
Class 3 devices SHALL satisfy baseline requirement SCP-060.
<<<
RELATIONS:
- TYPE: Parent
  VALUE: SCP-060
  ROLE: Refines

[REQUIREMENT]
UID: C3-SCP-090
STATUS: Draft
TAGS: NEEDS_WORKING_GROUP_REVIEW
STATEMENT: >>>
Class 3 devices SHALL satisfy baseline requirement SCP-090.
<<<
RELATIONS:
- TYPE: Parent
  VALUE: SCP-090
  ROLE: Refines

[REQUIREMENT]
UID: C3-SCP-091
STATUS: Draft
TAGS: NEEDS_WORKING_GROUP_REVIEW
STATEMENT: >>>
Class 3 devices SHALL satisfy baseline requirement SCP-091.
<<<
RELATIONS:
- TYPE: Parent
  VALUE: SCP-091
  ROLE: Refines

[REQUIREMENT]
UID: C3-SCP-092
STATUS: Draft
TAGS: NEEDS_WORKING_GROUP_REVIEW
STATEMENT: >>>
Class 3 devices SHALL satisfy baseline requirement SCP-092.
<<<
RELATIONS:
- TYPE: Parent
  VALUE: SCP-092
  ROLE: Refines

[REQUIREMENT]
UID: C3-SCP-100
STATUS: Draft
TAGS: NEEDS_WORKING_GROUP_REVIEW
STATEMENT: >>>
Class 3 devices SHALL satisfy baseline requirement SCP-100.
<<<
RELATIONS:
- TYPE: Parent
  VALUE: SCP-100
  ROLE: Refines

[REQUIREMENT]
UID: C3-SCP-110
STATUS: Draft
TAGS: NEEDS_WORKING_GROUP_REVIEW
STATEMENT: >>>
Class 3 devices SHALL satisfy baseline requirement SCP-110.
<<<
RELATIONS:
- TYPE: Parent
  VALUE: SCP-110
  ROLE: Refines

[REQUIREMENT]
UID: C3-SCP-120
STATUS: Draft
TAGS: NEEDS_WORKING_GROUP_REVIEW
STATEMENT: >>>
Class 3 devices SHALL satisfy baseline requirement SCP-120.
<<<
RELATIONS:
- TYPE: Parent
  VALUE: SCP-120
  ROLE: Refines

[REQUIREMENT]
UID: C3-SCP-130
STATUS: Draft
TAGS: NEEDS_WORKING_GROUP_REVIEW
STATEMENT: >>>
Class 3 devices SHALL satisfy baseline requirement SCP-130.
<<<
RELATIONS:
- TYPE: Parent
  VALUE: SCP-130
  ROLE: Refines

[REQUIREMENT]
UID: C3-SCP-140
STATUS: Draft
TAGS: NEEDS_WORKING_GROUP_REVIEW
STATEMENT: >>>
Class 3 devices SHALL satisfy baseline requirement SCP-140.
<<<
RELATIONS:
- TYPE: Parent
  VALUE: SCP-140
  ROLE: Refines

[REQUIREMENT]
UID: C3-SII-010
STATUS: Draft
TAGS: NEEDS_WORKING_GROUP_REVIEW
STATEMENT: >>>
Class 3 devices SHALL satisfy baseline requirement SII-010.
<<<
RELATIONS:
- TYPE: Parent
  VALUE: SII-010
  ROLE: Refines

[REQUIREMENT]
UID: C3-SII-011
STATUS: Draft
TAGS: NEEDS_WORKING_GROUP_REVIEW
STATEMENT: >>>
Class 3 devices SHALL satisfy baseline requirement SII-011.
<<<
RELATIONS:
- TYPE: Parent
  VALUE: SII-011
  ROLE: Refines

[REQUIREMENT]
UID: C3-SII-020
STATUS: Draft
TAGS: NEEDS_WORKING_GROUP_REVIEW
STATEMENT: >>>
Class 3 devices SHALL satisfy baseline requirement SII-020.
<<<
RELATIONS:
- TYPE: Parent
  VALUE: SII-020
  ROLE: Refines

[REQUIREMENT]
UID: C3-SII-021
STATUS: Draft
TAGS: NEEDS_WORKING_GROUP_REVIEW
STATEMENT: >>>
Class 3 devices SHALL satisfy baseline requirement SII-021.
<<<
RELATIONS:
- TYPE: Parent
  VALUE: SII-021
  ROLE: Refines

[REQUIREMENT]
UID: C3-SII-030
STATUS: Draft
TAGS: NEEDS_WORKING_GROUP_REVIEW
STATEMENT: >>>
Class 3 devices SHALL satisfy baseline requirement SII-030.
<<<
RELATIONS:
- TYPE: Parent
  VALUE: SII-030
  ROLE: Refines

[REQUIREMENT]
UID: C3-SII-040
STATUS: Draft
TAGS: NEEDS_WORKING_GROUP_REVIEW
STATEMENT: >>>
Class 3 devices SHALL satisfy baseline requirement SII-040.
<<<
RELATIONS:
- TYPE: Parent
  VALUE: SII-040
  ROLE: Refines

[REQUIREMENT]
UID: C3-SII-041
STATUS: Draft
TAGS: NEEDS_WORKING_GROUP_REVIEW
STATEMENT: >>>
Class 3 devices SHALL satisfy baseline requirement SII-041.
<<<
RELATIONS:
- TYPE: Parent
  VALUE: SII-041
  ROLE: Refines

[REQUIREMENT]
UID: C3-SII-060
STATUS: Draft
TAGS: NEEDS_WORKING_GROUP_REVIEW
STATEMENT: >>>
Class 3 devices SHALL satisfy baseline requirement SII-060.
<<<
RELATIONS:
- TYPE: Parent
  VALUE: SII-060
  ROLE: Refines

[REQUIREMENT]
UID: C3-SII-070
STATUS: Draft
TAGS: NEEDS_WORKING_GROUP_REVIEW
STATEMENT: >>>
Class 3 devices SHALL satisfy baseline requirement SII-070.
<<<
RELATIONS:
- TYPE: Parent
  VALUE: SII-070
  ROLE: Refines

[REQUIREMENT]
UID: C3-SII-071
STATUS: Draft
TAGS: NEEDS_WORKING_GROUP_REVIEW
STATEMENT: >>>
Class 3 devices SHALL satisfy baseline requirement SII-071.
<<<
RELATIONS:
- TYPE: Parent
  VALUE: SII-071
  ROLE: Refines

[REQUIREMENT]
UID: C3-SII-080
STATUS: Draft
TAGS: NEEDS_WORKING_GROUP_REVIEW
STATEMENT: >>>
Class 3 devices SHALL satisfy baseline requirement SII-080.
<<<
RELATIONS:
- TYPE: Parent
  VALUE: SII-080
  ROLE: Refines

[REQUIREMENT]
UID: C3-SII-081
STATUS: Draft
TAGS: NEEDS_WORKING_GROUP_REVIEW
STATEMENT: >>>
Class 3 devices SHALL satisfy baseline requirement SII-081.
<<<
RELATIONS:
- TYPE: Parent
  VALUE: SII-081
  ROLE: Refines

[REQUIREMENT]
UID: C3-SII-090
STATUS: Draft
TAGS: NEEDS_WORKING_GROUP_REVIEW
STATEMENT: >>>
Class 3 devices SHALL satisfy baseline requirement SII-090.
<<<
RELATIONS:
- TYPE: Parent
  VALUE: SII-090
  ROLE: Refines

[REQUIREMENT]
UID: C3-SII-100
STATUS: Draft
TAGS: NEEDS_WORKING_GROUP_REVIEW
STATEMENT: >>>
Class 3 devices SHALL satisfy baseline requirement SII-100.
<<<
RELATIONS:
- TYPE: Parent
  VALUE: SII-100
  ROLE: Refines

[REQUIREMENT]
UID: C3-SII-110
STATUS: Draft
TAGS: NEEDS_WORKING_GROUP_REVIEW
STATEMENT: >>>
Class 3 devices SHALL satisfy baseline requirement SII-110.
<<<
RELATIONS:
- TYPE: Parent
  VALUE: SII-110
  ROLE: Refines

[REQUIREMENT]
UID: C3-SII-120
STATUS: Draft
TAGS: NEEDS_WORKING_GROUP_REVIEW
STATEMENT: >>>
Class 3 devices SHALL satisfy baseline requirement SII-120.
<<<
RELATIONS:
- TYPE: Parent
  VALUE: SII-120
  ROLE: Refines

[REQUIREMENT]
UID: C3-SII-130
STATUS: Draft
TAGS: NEEDS_WORKING_GROUP_REVIEW
STATEMENT: >>>
Class 3 devices SHALL satisfy baseline requirement SII-130.
<<<
RELATIONS:
- TYPE: Parent
  VALUE: SII-130
  ROLE: Refines

[REQUIREMENT]
UID: C3-SII-140
STATUS: Draft
TAGS: NEEDS_WORKING_GROUP_REVIEW
STATEMENT: >>>
Class 3 devices SHALL satisfy baseline requirement SII-140.
<<<
RELATIONS:
- TYPE: Parent
  VALUE: SII-140
  ROLE: Refines

[REQUIREMENT]
UID: C3-SII-150
STATUS: Draft
TAGS: NEEDS_WORKING_GROUP_REVIEW
STATEMENT: >>>
Class 3 devices SHALL satisfy baseline requirement SII-150.
<<<
RELATIONS:
- TYPE: Parent
  VALUE: SII-150
  ROLE: Refines

[REQUIREMENT]
UID: C3-SII-170
STATUS: Draft
TAGS: NEEDS_WORKING_GROUP_REVIEW
STATEMENT: >>>
Class 3 devices SHALL satisfy baseline requirement SII-170.
<<<
RELATIONS:
- TYPE: Parent
  VALUE: SII-170
  ROLE: Refines

[REQUIREMENT]
UID: C3-SII-171
STATUS: Draft
TAGS: NEEDS_WORKING_GROUP_REVIEW
STATEMENT: >>>
Class 3 devices SHALL satisfy baseline requirement SII-171.
<<<
RELATIONS:
- TYPE: Parent
  VALUE: SII-171
  ROLE: Refines

[REQUIREMENT]
UID: C3-SII-180
STATUS: Draft
TAGS: NEEDS_WORKING_GROUP_REVIEW
STATEMENT: >>>
Class 3 devices SHALL satisfy baseline requirement SII-180.
<<<
RELATIONS:
- TYPE: Parent
  VALUE: SII-180
  ROLE: Refines

[REQUIREMENT]
UID: C3-SII-190
STATUS: Draft
TAGS: NEEDS_WORKING_GROUP_REVIEW
STATEMENT: >>>
Class 3 devices SHALL satisfy baseline requirement SII-190.
<<<
RELATIONS:
- TYPE: Parent
  VALUE: SII-190
  ROLE: Refines

[REQUIREMENT]
UID: C3-SII-200
STATUS: Draft
TAGS: NEEDS_WORKING_GROUP_REVIEW
STATEMENT: >>>
Class 3 devices SHALL satisfy baseline requirement SII-200.
<<<
RELATIONS:
- TYPE: Parent
  VALUE: SII-200
  ROLE: Refines

[[/SECTION]]

[[SECTION]]
TITLE: Vehicle Bus Connection Security Requirements Applicability

[REQUIREMENT]
UID: C3-VEH-AC-010
STATUS: Draft
TAGS: NEEDS_WORKING_GROUP_REVIEW
STATEMENT: >>>
Class 3 vehicle network interfaces SHALL satisfy requirement VEH-AC-010.
<<<
RELATIONS:
- TYPE: Parent
  VALUE: VEH-AC-010
  ROLE: Refines

[REQUIREMENT]
UID: C3-VEH-AC-020
STATUS: Draft
TAGS: NEEDS_WORKING_GROUP_REVIEW
STATEMENT: >>>
Class 3 vehicle network interfaces SHALL satisfy requirement VEH-AC-020.
<<<
RELATIONS:
- TYPE: Parent
  VALUE: VEH-AC-020
  ROLE: Refines

[REQUIREMENT]
UID: C3-VEH-AC-030
STATUS: Draft
TAGS: NEEDS_WORKING_GROUP_REVIEW
STATEMENT: >>>
Class 3 vehicle network interfaces SHALL satisfy requirement VEH-AC-030.
<<<
RELATIONS:
- TYPE: Parent
  VALUE: VEH-AC-030
  ROLE: Refines

[REQUIREMENT]
UID: C3-VEH-AC-040
STATUS: Draft
TAGS: NEEDS_WORKING_GROUP_REVIEW
STATEMENT: >>>
Class 3 vehicle network interfaces SHALL satisfy requirement VEH-AC-040.
<<<
RELATIONS:
- TYPE: Parent
  VALUE: VEH-AC-040
  ROLE: Refines

[REQUIREMENT]
UID: C3-VEH-AC-041
STATUS: Draft
TAGS: NEEDS_WORKING_GROUP_REVIEW
STATEMENT: >>>
Class 3 vehicle network interfaces SHALL satisfy requirement VEH-AC-041.
<<<
RELATIONS:
- TYPE: Parent
  VALUE: VEH-AC-041
  ROLE: Refines

[REQUIREMENT]
UID: C3-VEH-AC-050
STATUS: Draft
TAGS: NEEDS_WORKING_GROUP_REVIEW
STATEMENT: >>>
Class 3 vehicle network interfaces SHALL satisfy requirement VEH-AC-050.
<<<
RELATIONS:
- TYPE: Parent
  VALUE: VEH-AC-050
  ROLE: Refines

[REQUIREMENT]
UID: C3-VEH-AC-080
STATUS: Draft
TAGS: NEEDS_WORKING_GROUP_REVIEW
STATEMENT: >>>
Class 3 vehicle network interfaces SHALL satisfy requirement VEH-AC-080.
<<<
RELATIONS:
- TYPE: Parent
  VALUE: VEH-AC-080
  ROLE: Refines

[REQUIREMENT]
UID: C3-VEH-CM-010
STATUS: Draft
TAGS: NEEDS_WORKING_GROUP_REVIEW
STATEMENT: >>>
Class 3 vehicle network interfaces SHALL satisfy requirement VEH-CM-010.
<<<
RELATIONS:
- TYPE: Parent
  VALUE: VEH-CM-010
  ROLE: Refines

[REQUIREMENT]
UID: C3-VEH-CM-020
STATUS: Draft
TAGS: NEEDS_WORKING_GROUP_REVIEW
STATEMENT: >>>
Class 3 vehicle network interfaces SHALL satisfy requirement VEH-CM-020.
<<<
RELATIONS:
- TYPE: Parent
  VALUE: VEH-CM-020
  ROLE: Refines

[REQUIREMENT]
UID: C3-VEH-CM-030
STATUS: Draft
TAGS: NEEDS_WORKING_GROUP_REVIEW
STATEMENT: >>>
Class 3 vehicle network interfaces SHALL satisfy requirement VEH-CM-030.
<<<
RELATIONS:
- TYPE: Parent
  VALUE: VEH-CM-030
  ROLE: Refines

[REQUIREMENT]
UID: C3-VEH-CM-040
STATUS: Draft
TAGS: NEEDS_WORKING_GROUP_REVIEW
STATEMENT: >>>
Class 3 vehicle network interfaces SHALL satisfy requirement VEH-CM-040.
<<<
RELATIONS:
- TYPE: Parent
  VALUE: VEH-CM-040
  ROLE: Refines

[REQUIREMENT]
UID: C3-VEH-IA-010
STATUS: Draft
TAGS: NEEDS_WORKING_GROUP_REVIEW
STATEMENT: >>>
Class 3 vehicle network interfaces SHALL satisfy requirement VEH-IA-010.
<<<
RELATIONS:
- TYPE: Parent
  VALUE: VEH-IA-010
  ROLE: Refines

[REQUIREMENT]
UID: C3-VEH-IA-020
STATUS: Draft
TAGS: NEEDS_WORKING_GROUP_REVIEW
STATEMENT: >>>
Class 3 vehicle network interfaces SHALL satisfy requirement VEH-IA-020.
<<<
RELATIONS:
- TYPE: Parent
  VALUE: VEH-IA-020
  ROLE: Refines

[REQUIREMENT]
UID: C3-VEH-IA-030
STATUS: Draft
TAGS: NEEDS_WORKING_GROUP_REVIEW
STATEMENT: >>>
Class 3 vehicle network interfaces SHALL satisfy requirement VEH-IA-030.
<<<
RELATIONS:
- TYPE: Parent
  VALUE: VEH-IA-030
  ROLE: Refines

[REQUIREMENT]
UID: C3-VEH-IR-010
STATUS: Draft
TAGS: NEEDS_WORKING_GROUP_REVIEW
STATEMENT: >>>
Class 3 vehicle network interfaces SHALL satisfy requirement VEH-IR-010.
<<<
RELATIONS:
- TYPE: Parent
  VALUE: VEH-IR-010
  ROLE: Refines

[REQUIREMENT]
UID: C3-VEH-M-010
STATUS: Draft
TAGS: NEEDS_WORKING_GROUP_REVIEW
STATEMENT: >>>
Class 3 vehicle network interfaces SHALL satisfy requirement VEH-M-010.
<<<
RELATIONS:
- TYPE: Parent
  VALUE: VEH-M-010
  ROLE: Refines

[REQUIREMENT]
UID: C3-VEH-M-040
STATUS: Draft
TAGS: NEEDS_WORKING_GROUP_REVIEW
STATEMENT: >>>
Class 3 vehicle network interfaces SHALL satisfy requirement VEH-M-040.
<<<
RELATIONS:
- TYPE: Parent
  VALUE: VEH-M-040
  ROLE: Refines

[REQUIREMENT]
UID: C3-VEH-PS-010
STATUS: Draft
TAGS: NEEDS_WORKING_GROUP_REVIEW
STATEMENT: >>>
Class 3 vehicle network interfaces SHALL satisfy requirement VEH-PS-010.
<<<
RELATIONS:
- TYPE: Parent
  VALUE: VEH-PS-010
  ROLE: Refines

[REQUIREMENT]
UID: C3-VEH-RA-010
STATUS: Draft
TAGS: NEEDS_WORKING_GROUP_REVIEW
STATEMENT: >>>
Class 3 vehicle network interfaces SHALL satisfy requirement VEH-RA-010.
<<<
RELATIONS:
- TYPE: Parent
  VALUE: VEH-RA-010
  ROLE: Refines

[REQUIREMENT]
UID: C3-VEH-RA-020
STATUS: Draft
TAGS: NEEDS_WORKING_GROUP_REVIEW
STATEMENT: >>>
Class 3 vehicle network interfaces SHALL satisfy requirement VEH-RA-020.
<<<
RELATIONS:
- TYPE: Parent
  VALUE: VEH-RA-020
  ROLE: Refines

[REQUIREMENT]
UID: C3-VEH-SAA-010
STATUS: Draft
TAGS: NEEDS_WORKING_GROUP_REVIEW
STATEMENT: >>>
Class 3 vehicle network interfaces SHALL satisfy requirement VEH-SAA-010.
<<<
RELATIONS:
- TYPE: Parent
  VALUE: VEH-SAA-010
  ROLE: Refines

[REQUIREMENT]
UID: C3-VEH-SAA-020
STATUS: Draft
TAGS: NEEDS_WORKING_GROUP_REVIEW
STATEMENT: >>>
Class 3 vehicle network interfaces SHALL satisfy requirement VEH-SAA-020.
<<<
RELATIONS:
- TYPE: Parent
  VALUE: VEH-SAA-020
  ROLE: Refines

[REQUIREMENT]
UID: C3-VEH-SAA-030
STATUS: Draft
TAGS: NEEDS_WORKING_GROUP_REVIEW
STATEMENT: >>>
Class 3 vehicle network interfaces SHALL satisfy requirement VEH-SAA-030.
<<<
RELATIONS:
- TYPE: Parent
  VALUE: VEH-SAA-030
  ROLE: Refines

[REQUIREMENT]
UID: C3-VEH-SAA-040
STATUS: Draft
TAGS: NEEDS_WORKING_GROUP_REVIEW
STATEMENT: >>>
Class 3 vehicle network interfaces SHALL satisfy requirement VEH-SAA-040.
<<<
RELATIONS:
- TYPE: Parent
  VALUE: VEH-SAA-040
  ROLE: Refines

[REQUIREMENT]
UID: C3-VEH-SAA-050
STATUS: Draft
TAGS: NEEDS_WORKING_GROUP_REVIEW
STATEMENT: >>>
Class 3 vehicle network interfaces SHALL satisfy requirement VEH-SAA-050.
<<<
RELATIONS:
- TYPE: Parent
  VALUE: VEH-SAA-050
  ROLE: Refines

[REQUIREMENT]
UID: C3-VEH-SCP-010
STATUS: Draft
TAGS: NEEDS_WORKING_GROUP_REVIEW
STATEMENT: >>>
Class 3 vehicle network interfaces SHALL satisfy requirement VEH-SCP-010.
<<<
RELATIONS:
- TYPE: Parent
  VALUE: VEH-SCP-010
  ROLE: Refines

[REQUIREMENT]
UID: C3-VEH-SCP-011
STATUS: Draft
TAGS: NEEDS_WORKING_GROUP_REVIEW
STATEMENT: >>>
Class 3 vehicle network interfaces SHALL satisfy requirement VEH-SCP-011.
<<<
RELATIONS:
- TYPE: Parent
  VALUE: VEH-SCP-011
  ROLE: Refines

[REQUIREMENT]
UID: C3-VEH-SCP-020
STATUS: Draft
TAGS: NEEDS_WORKING_GROUP_REVIEW
STATEMENT: >>>
Class 3 vehicle network interfaces SHALL satisfy requirement VEH-SCP-020.
<<<
RELATIONS:
- TYPE: Parent
  VALUE: VEH-SCP-020
  ROLE: Refines

[REQUIREMENT]
UID: C3-VEH-SCP-030
STATUS: Draft
TAGS: NEEDS_WORKING_GROUP_REVIEW
STATEMENT: >>>
Class 3 vehicle network interfaces SHALL satisfy requirement VEH-SCP-030.
<<<
RELATIONS:
- TYPE: Parent
  VALUE: VEH-SCP-030
  ROLE: Refines

[REQUIREMENT]
UID: C3-VEH-SCP-040
STATUS: Draft
TAGS: NEEDS_WORKING_GROUP_REVIEW
STATEMENT: >>>
Class 3 vehicle network interfaces SHALL satisfy requirement VEH-SCP-040.
<<<
RELATIONS:
- TYPE: Parent
  VALUE: VEH-SCP-040
  ROLE: Refines

[REQUIREMENT]
UID: C3-VEH-SCP-060
STATUS: Draft
TAGS: NEEDS_WORKING_GROUP_REVIEW
STATEMENT: >>>
Class 3 vehicle network interfaces SHALL satisfy requirement VEH-SCP-060.
<<<
RELATIONS:
- TYPE: Parent
  VALUE: VEH-SCP-060
  ROLE: Refines

[REQUIREMENT]
UID: C3-VEH-SCP-100
STATUS: Draft
TAGS: NEEDS_WORKING_GROUP_REVIEW
STATEMENT: >>>
Class 3 vehicle network interfaces SHALL satisfy requirement VEH-SCP-100.
<<<
RELATIONS:
- TYPE: Parent
  VALUE: VEH-SCP-100
  ROLE: Refines

[REQUIREMENT]
UID: C3-VEH-SCP-140
STATUS: Draft
TAGS: NEEDS_WORKING_GROUP_REVIEW
STATEMENT: >>>
Class 3 vehicle network interfaces SHALL satisfy requirement VEH-SCP-140.
<<<
RELATIONS:
- TYPE: Parent
  VALUE: VEH-SCP-140
  ROLE: Refines

[REQUIREMENT]
UID: C3-VEH-SII-010
STATUS: Draft
TAGS: NEEDS_WORKING_GROUP_REVIEW
STATEMENT: >>>
Class 3 vehicle network interfaces SHALL satisfy requirement VEH-SII-010.
<<<
RELATIONS:
- TYPE: Parent
  VALUE: VEH-SII-010
  ROLE: Refines

[REQUIREMENT]
UID: C3-VEH-SII-011
STATUS: Draft
TAGS: NEEDS_WORKING_GROUP_REVIEW
STATEMENT: >>>
Class 3 vehicle network interfaces SHALL satisfy requirement VEH-SII-011.
<<<
RELATIONS:
- TYPE: Parent
  VALUE: VEH-SII-011
  ROLE: Refines

[REQUIREMENT]
UID: C3-VEH-SII-020
STATUS: Draft
TAGS: NEEDS_WORKING_GROUP_REVIEW
STATEMENT: >>>
Class 3 vehicle network interfaces SHALL satisfy requirement VEH-SII-020.
<<<
RELATIONS:
- TYPE: Parent
  VALUE: VEH-SII-020
  ROLE: Refines

[REQUIREMENT]
UID: C3-VEH-SII-021
STATUS: Draft
TAGS: NEEDS_WORKING_GROUP_REVIEW
STATEMENT: >>>
Class 3 vehicle network interfaces SHALL satisfy requirement VEH-SII-021.
<<<
RELATIONS:
- TYPE: Parent
  VALUE: VEH-SII-021
  ROLE: Refines

[REQUIREMENT]
UID: C3-VEH-SII-030
STATUS: Draft
TAGS: NEEDS_WORKING_GROUP_REVIEW
STATEMENT: >>>
Class 3 vehicle network interfaces SHALL satisfy requirement VEH-SII-030.
<<<
RELATIONS:
- TYPE: Parent
  VALUE: VEH-SII-030
  ROLE: Refines

[REQUIREMENT]
UID: C3-VEH-SII-040
STATUS: Draft
TAGS: NEEDS_WORKING_GROUP_REVIEW
STATEMENT: >>>
Class 3 vehicle network interfaces SHALL satisfy requirement VEH-SII-040.
<<<
RELATIONS:
- TYPE: Parent
  VALUE: VEH-SII-040
  ROLE: Refines

[REQUIREMENT]
UID: C3-VEH-SII-041
STATUS: Draft
TAGS: NEEDS_WORKING_GROUP_REVIEW
STATEMENT: >>>
Class 3 vehicle network interfaces SHALL satisfy requirement VEH-SII-041.
<<<
RELATIONS:
- TYPE: Parent
  VALUE: VEH-SII-041
  ROLE: Refines

[REQUIREMENT]
UID: C3-VEH-SII-060
STATUS: Draft
TAGS: NEEDS_WORKING_GROUP_REVIEW
STATEMENT: >>>
Class 3 vehicle network interfaces SHALL satisfy requirement VEH-SII-060.
<<<
RELATIONS:
- TYPE: Parent
  VALUE: VEH-SII-060
  ROLE: Refines

[REQUIREMENT]
UID: C3-VEH-SII-070
STATUS: Draft
TAGS: NEEDS_WORKING_GROUP_REVIEW
STATEMENT: >>>
Class 3 vehicle network interfaces SHALL satisfy requirement VEH-SII-070.
<<<
RELATIONS:
- TYPE: Parent
  VALUE: VEH-SII-070
  ROLE: Refines

[REQUIREMENT]
UID: C3-VEH-SII-071
STATUS: Draft
TAGS: NEEDS_WORKING_GROUP_REVIEW
STATEMENT: >>>
Class 3 vehicle network interfaces SHALL satisfy requirement VEH-SII-071.
<<<
RELATIONS:
- TYPE: Parent
  VALUE: VEH-SII-071
  ROLE: Refines

[REQUIREMENT]
UID: C3-VEH-SII-080
STATUS: Draft
TAGS: NEEDS_WORKING_GROUP_REVIEW
STATEMENT: >>>
Class 3 vehicle network interfaces SHALL satisfy requirement VEH-SII-080.
<<<
RELATIONS:
- TYPE: Parent
  VALUE: VEH-SII-080
  ROLE: Refines

[REQUIREMENT]
UID: C3-VEH-SII-081
STATUS: Draft
TAGS: NEEDS_WORKING_GROUP_REVIEW
STATEMENT: >>>
Class 3 vehicle network interfaces SHALL satisfy requirement VEH-SII-081.
<<<
RELATIONS:
- TYPE: Parent
  VALUE: VEH-SII-081
  ROLE: Refines

[REQUIREMENT]
UID: C3-VEH-SII-090
STATUS: Draft
TAGS: NEEDS_WORKING_GROUP_REVIEW
STATEMENT: >>>
Class 3 vehicle network interfaces SHALL satisfy requirement VEH-SII-090.
<<<
RELATIONS:
- TYPE: Parent
  VALUE: VEH-SII-090
  ROLE: Refines

[REQUIREMENT]
UID: C3-VEH-SII-120
STATUS: Draft
TAGS: NEEDS_WORKING_GROUP_REVIEW
STATEMENT: >>>
Class 3 vehicle network interfaces SHALL satisfy requirement VEH-SII-120.
<<<
RELATIONS:
- TYPE: Parent
  VALUE: VEH-SII-120
  ROLE: Refines

[REQUIREMENT]
UID: C3-VEH-SII-130
STATUS: Draft
TAGS: NEEDS_WORKING_GROUP_REVIEW
STATEMENT: >>>
Class 3 vehicle network interfaces SHALL satisfy requirement VEH-SII-130.
<<<
RELATIONS:
- TYPE: Parent
  VALUE: VEH-SII-130
  ROLE: Refines

[REQUIREMENT]
UID: C3-VEH-SII-140
STATUS: Draft
TAGS: NEEDS_WORKING_GROUP_REVIEW
STATEMENT: >>>
Class 3 vehicle network interfaces SHALL satisfy requirement VEH-SII-140.
<<<
RELATIONS:
- TYPE: Parent
  VALUE: VEH-SII-140
  ROLE: Refines

[REQUIREMENT]
UID: C3-VEH-SII-150
STATUS: Draft
TAGS: NEEDS_WORKING_GROUP_REVIEW
STATEMENT: >>>
Class 3 vehicle network interfaces SHALL satisfy requirement VEH-SII-150.
<<<
RELATIONS:
- TYPE: Parent
  VALUE: VEH-SII-150
  ROLE: Refines

[REQUIREMENT]
UID: C3-VEH-SII-170
STATUS: Draft
TAGS: NEEDS_WORKING_GROUP_REVIEW
STATEMENT: >>>
Class 3 vehicle network interfaces SHALL satisfy requirement VEH-SII-170.
<<<
RELATIONS:
- TYPE: Parent
  VALUE: VEH-SII-170
  ROLE: Refines

[REQUIREMENT]
UID: C3-VEH-SII-171
STATUS: Draft
TAGS: NEEDS_WORKING_GROUP_REVIEW
STATEMENT: >>>
Class 3 vehicle network interfaces SHALL satisfy requirement VEH-SII-171.
<<<
RELATIONS:
- TYPE: Parent
  VALUE: VEH-SII-171
  ROLE: Refines

[REQUIREMENT]
UID: C3-VEH-SII-180
STATUS: Draft
TAGS: NEEDS_WORKING_GROUP_REVIEW
STATEMENT: >>>
Class 3 vehicle network interfaces SHALL satisfy requirement VEH-SII-180.
<<<
RELATIONS:
- TYPE: Parent
  VALUE: VEH-SII-180
  ROLE: Refines

[REQUIREMENT]
UID: C3-VEH-SII-200
STATUS: Draft
TAGS: NEEDS_WORKING_GROUP_REVIEW
STATEMENT: >>>
Class 3 vehicle network interfaces SHALL satisfy requirement VEH-SII-200.
<<<
RELATIONS:
- TYPE: Parent
  VALUE: VEH-SII-200
  ROLE: Refines

[[/SECTION]]
